# Specification: Specification Document
- Description: Requirements Document

## R1
- String: Start editing here.

## R2
- String: Hello

## R3
- Bool: false
- Date: 2014-07-05T00:00:00.000+02:00
- Integer: 3
- Enum1: One
- Enum2: One
- Real: 0.0
- String: Hello
  World.

### R4
- Bool: false
- Real: 5.1
- Enum1: Two

## R5
- Bool: false

### R6
- Bool: false
- Real: 5.2
- Enum1: Three

### R7
- Bool: true
- String: Foo
- Real: 4.3
- Enum2: One, Two, Three

## R8

### R9

### R10

### R11
