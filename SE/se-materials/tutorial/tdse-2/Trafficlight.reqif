# Specification: Specification Document
- Description: Requirements Document

## R6 (Headline Type)
Requirements

### REQ-1 (Requirements Type)
The system shall allow pedestrians to safely cross a street.

### R7 (Information Type)
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
### REQ-2 (Requirements Type)
The system scope is a controller that drives the existing [CarLight] ([red], [yellow], [green]) and [PedLight] ([red], [green]).

### REQ-3 (Requirements Type)
[CarLight] and [PedestrianLight] must never be green at the same time.

### REQ-4 (Requirements Type)
A timer sends a [Tick] to the controller every second.

### REQ-5 (Requirements Type)
The traffic light follows a standard light regime.

# Specification
- Description: Glossary

## R8 (Headline Type)
Glossary

### R9 (Term Type)
The signal for the pedestrians, with the colors red and green
- Term: PedLight

### R10 (Term Type)
The signal for the cars, with the colors red, yellow and green
- Term: CarLight

### R11 (Term Type)
Standard color
- Term: red

### R12 (Term Type)
Standard color
- Term: yellow

### R13 (Term Type)
Standard color
- Term: green

### R14 (Term Type)
An external regular trigger with a frequency of 1 Hz.
- Term: Tick
