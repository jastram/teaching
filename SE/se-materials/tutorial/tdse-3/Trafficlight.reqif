# Specification: Specification Document
- Description: Requirements Document

## R10 (Headline Type)
Requirements

### REQ-1 (Requirements Type)
The system shall allow pedestrians to safely cross a street.

### R11 (Information Type)
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
### REQ-2 (Requirements Type)
The system scope is a controller that drives the existing CarLight (red, yellow, green) and PedLight (red, green).
- Trace Type -> R1
- Trace Type -> R3
- Trace Type -> R4

### REQ-3 (Requirements Type)
CarLight and PedestrianLight must never be green at the same time.

### REQ-4 (Requirements Type)
A timer sends a Tick to the controller every second.
- Trace Type -> R2

### REQ-5 (Requirements Type)
The traffic light follows a standard light regime.

## R1 (Proxy Type)
platform:/resource/tdse-3/model/tdse3.ecore#//Controller
Controller
abstract=false
defaultValue=null
instanceClass=null
instanceClassName=null
instanceTypeName=null
interface=false
name=Controller

## R2 (Proxy Type)
platform:/resource/tdse-3/model/tdse3.ecore#//Controller/tick
tick() / Controller
lowerBound=1
many=false
name=tick
ordered=true
required=true
unique=true
upperBound=1

## R3 (Proxy Type)
platform:/resource/tdse-3/model/tdse3.ecore#//PedLight
PedLight
abstract=false
defaultValue=null
instanceClass=null
instanceClassName=null
instanceTypeName=null
interface=false
name=PedLight

## R4 (Proxy Type)
platform:/resource/tdse-3/model/tdse3.ecore#//CarLight
CarLight
abstract=false
defaultValue=null
instanceClass=null
instanceClassName=null
instanceTypeName=null
interface=false
name=CarLight
