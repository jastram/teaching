# Specification: Specification Document
- Description: Requirements Document

## R6 (Headline Type)
Requirements

### REQ-1 (Requirements Type)
The system shall allow pedestrians to safely cross a street.

### R7 (Information Type)
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
### REQ-2 (Requirements Type)
The system scope is a controller that drives the existing lights for cars (red, yellow, green) and pedestrians (red, green).

### REQ-3 (Requirements Type)
The lights for cars and pedestrians must never be green at the same time.

### REQ-4 (Requirements Type)
A timer sends a pulse to the controller every second.

### REQ-5 (Requirements Type)
The traffic light follows a standard light regime.
